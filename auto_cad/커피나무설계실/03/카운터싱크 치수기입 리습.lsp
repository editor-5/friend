;카운터싱크 치수기입 리습
(DEFUN C:S3 () (COMMAND "LEADER" "_NEA" pause pause "" "%%C3.5 DRILL" "C/S90 %%D DP1.6" ""))
(DEFUN C:S4 () (COMMAND "LEADER" "_NEA" pause pause "" "%%C4.5 DRILL" "C/S90 %%D DP2" ""))
(DEFUN C:S5 () (COMMAND "LEADER" "_NEA" pause pause "" "%%C5.5 DRILL" "C/S90 %%D DP2.6" ""))
(DEFUN C:S6 () (COMMAND "LEADER" "_NEA" pause pause "" "%%C6.5 DRILL" "C/S90 %%D DP3.2" ""))
(DEFUN C:S8 () (COMMAND "LEADER" "_NEA" pause pause "" "%%C9 DRILL" "C/S90 %%D DP4.1" ""))


(DEFUN C:S3B () (COMMAND "LEADER" "_NEA" pause pause "" "%%C3.5 DRILL" "C/S90 %%D DP1.6 배면가공" ""))
(DEFUN C:S4B () (COMMAND "LEADER" "_NEA" pause pause "" "%%C4.5 DRILL" "C/S90 %%D DP2 배면가공" ""))
(DEFUN C:S5B () (COMMAND "LEADER" "_NEA" pause pause "" "%%C5.5 DRILL" "C/S90 %%D DP2.6 배면가공" ""))
(DEFUN C:S6B () (COMMAND "LEADER" "_NEA" pause pause "" "%%C7 DRILL" "C/S90 %%D DP3.2 배면가공" ""))
(DEFUN C:S8B () (COMMAND "LEADER" "_NEA" pause pause "" "%%C9 DRILL" "C/S90 %%D DP4.1 배면가공" ""))
