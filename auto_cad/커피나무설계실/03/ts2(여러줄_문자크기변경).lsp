(defun c:ts2()
   (setq ts(ssget "_:L" (list (cons 0 "*text"))))
   (setq l(sslength ts))
   (setq sz(getreal"\n Text Size : "))
   (setq i 0)
   (setq l1(- l 1))
   (while (<= i l1)
        (setq t1(ssname ts i))
        (setq t2(entget t1))
        (setq t0(cdr (assoc 0 t2)))
      (cond ((or (= "MTEXT" t0) (= "TEXT" t0))
            (setq h sz)
            (setq t2(subst (cons 40 h)(assoc 40 t2) t2))
            (entmod t2))
            (t nill)
       )
     (setq i(+ i 1))
  )
 )
