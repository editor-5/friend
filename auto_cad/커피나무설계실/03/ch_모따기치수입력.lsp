;모따기 치수입력
(defun C:CH0.5 () (command "LEADER" "_MID" pause pause "" "C0.5" ""))
(defun C:CH1 ()  (command "LEADER" "_MID" pause pause "" "C1" ""))
(defun C:CH2 ()  (command "LEADER" "_MID" pause pause "" "C2" ""))
(defun C:CH3 ()  (command "LEADER" "_MID" pause pause "" "C3" ""))
(defun C:CH4 ()  (command "LEADER" "_MID" pause pause "" "C4" ""))
(defun C:CH5 ()  (command "LEADER" "_MID" pause pause "" "C5" ""))
(defun C:CH6 ()  (command "LEADER" "_MID" pause pause "" "C6" ""))
(defun C:CH7 ()  (command "LEADER" "_MID" pause pause "" "C7" ""))
(defun C:CH8 ()  (command "LEADER" "_MID" pause pause "" "C8" ""))
(defun C:CH9 ()  (command "LEADER" "_MID" pause pause "" "C9" ""))
(defun C:CH10 ()  (command "LEADER" "_MID" pause pause "" "C10" ""))
(defun C:CH15 ()  (command "LEADER" "_MID" pause pause "" "C15" ""))
(defun C:CH20 ()  (command "LEADER" "_MID" pause pause "" "C20" ""))
