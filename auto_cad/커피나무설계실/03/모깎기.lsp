; [모깎기를 만듭니다 - 간격주의]
(defun c:f()(command "fillet" "T" "T" "r" "0" "fillet" ))
(defun c:f1()(command "fillet" "T" "T" "r" "1" "fillet" ))
(defun c:f2()(command "fillet" "T" "T" "r" "2" "fillet" ))
(defun c:f3()(command "fillet" "T" "T" "r" "3" "fillet" ))
(defun c:f4()(command "fillet" "T" "T" "r" "4" "fillet" ))
(defun c:f5()(command "fillet" "T" "T" "r" "5" "fillet" ))
(defun c:f6()(command "fillet" "T" "T" "r" "6" "fillet" ))
(defun c:f7()(command "fillet" "T" "T" "r" "7" "fillet" ))
(defun c:f8()(command "fillet" "T" "T" "r" "8" "fillet" ))
(defun c:f9()(command "fillet" "T" "T" "r" "9" "fillet" ))
(defun c:f10()(command "fillet" "T" "T" "r" "10" "fillet" ))
(defun c:f15()(command "fillet" "T" "T" "r" "15" "fillet" ))
(defun c:f20()(command "fillet" "T" "T" "r" "20" "fillet" ))
(defun c:f25()(command "fillet" "T" "T" "r" "25" "fillet" ))
(defun c:f30()(command "fillet" "T" "T" "r" "30" "fillet" ))
(defun c:f35()(command "fillet" "T" "T" "r" "35" "fillet" ))
(defun c:f40()(command "fillet" "T" "T" "r" "40" "fillet" ))
(defun c:f45()(command "fillet" "T" "T" "r" "45" "fillet" ))
(defun c:f50()(command "fillet" "T" "T" "r" "50" "fillet" ))
(defun c:f55()(command "fillet" "T" "T" "r" "55" "fillet" ))
(defun c:f60()(command "fillet" "T" "T" "r" "60" "fillet" ))
(defun c:f65()(command "fillet" "T" "T" "r" "65" "fillet" ))
(defun c:f70()(command "fillet" "T" "T" "r" "70" "fillet" ))
(defun c:f75()(command "fillet" "T" "T" "r" "75" "fillet" ))
(defun c:f80()(command "fillet" "T" "T" "r" "80" "fillet" ))
(defun c:f85()(command "fillet" "T" "T" "r" "85" "fillet" ))
(defun c:f90()(command "fillet" "T" "T" "r" "90" "fillet" ))
(defun c:f95()(command "fillet" "T" "T" "r" "95" "fillet" ))
(defun c:f100()(command "fillet" "T" "T" "r" "100" "fillet" ))
