; 카운터보어 기입용 리습
(DEFUN C:C3 () (COMMAND "LEADER" "_NEA" pause pause "" "%%C3.5 DRILL" "C/B %%C6 DP3.6" ""))
(DEFUN C:C4 () (COMMAND "LEADER" "_NEA" pause pause "" "%%C4.5 DRILL" "C/B %%C8 DP4.6" ""))
(DEFUN C:C5 () (COMMAND "LEADER" "_NEA" pause pause "" "%%C5.5 DRILL" "C/B %%C9.5 DP5.6" ""))
(DEFUN C:C6 () (COMMAND "LEADER" "_NEA" pause pause "" "%%C6.5 DRILL" "C/B %%C11 DP6.6" ""))
(DEFUN C:C8 () (COMMAND "LEADER" "_NEA" pause pause "" "%%C9 DRILL" "C/B %%C14 DP8.6" ""))
(DEFUN C:C10 () (COMMAND "LEADER" "_NEA" pause pause "" "%%C11 DRILL" "C/B %%C17.5 DP10.3" ""))
(DEFUN C:C12 () (COMMAND "LEADER" "_NEA" pause pause "" "%%C14 DRILL" "C/B %%C20 DP13" ""))

(DEFUN C:C3B () (COMMAND "LEADER" "_NEA" pause pause "" "%%C3.5 DRILL" "C/B %%C6 DP3.6 배면가공" ""))
(DEFUN C:C4B () (COMMAND "LEADER" "_NEA" pause pause "" "%%C4.5 DRILL" "C/B %%C8 DP4.6 배면가공" ""))
(DEFUN C:C5B () (COMMAND "LEADER" "_NEA" pause pause "" "%%C5.5 DRILL" "C/B %%C9.5 DP5.6 배면가공" ""))
(DEFUN C:C6B () (COMMAND "LEADER" "_NEA" pause pause "" "%%C6.5 DRILL" "C/B %%C11 DP6.6 배면가공" ""))
(DEFUN C:C8B () (COMMAND "LEADER" "_NEA" pause pause "" "%%C9 DRILL" "C/B %%C14 DP8.6 배면가공" ""))
(DEFUN C:C10B () (COMMAND "LEADER" "_NEA" pause pause "" "%%C11 DRILL" "C/B %%C17.5 DP11 배면가공" ""))
(DEFUN C:C12B () (COMMAND "LEADER" "_NEA" pause pause "" "%%C14 DRILL" "C/B %%C20 DP13 배면가공" ""))
