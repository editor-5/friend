; [모따기를 만듭니다 - 간격주의]
(defun c:cc1() (command "chamfer" "D" "1" "1" "chamfer"))
(defun c:cc2() (command "chamfer" "D" "2" "2" "chamfer")) 
(defun c:cc3() (command "chamfer" "D" "3" "3" "chamfer")) 
(defun c:cc4() (command "chamfer" "D" "4" "4" "chamfer")) 
(defun c:cc5() (command "chamfer" "D" "5" "5" "chamfer"))
(defun c:cc6() (command "chamfer" "D" "6" "6" "chamfer"))
(defun c:cc7() (command "chamfer" "D" "7" "7" "chamfer"))
(defun c:cc8() (command "chamfer" "D" "8" "8" "chamfer"))
(defun c:cc9() (command "chamfer" "D" "9" "9" "chamfer"))
(defun c:cc10() (command "chamfer" "D" "10" "10" "chamfer")) 
(defun c:cc15() (command "chamfer" "D" "15" "15" "chamfer")) 
(defun c:cc20() (command "chamfer" "D" "20" "20" "chamfer")) 
(defun c:cc25() (command "chamfer" "D" "25" "25" "chamfer")) 
(defun c:cc30() (command "chamfer" "D" "30" "30" "chamfer")) 
(defun c:cc35() (command "chamfer" "D" "35" "35" "chamfer")) 
(defun c:cc40() (command "chamfer" "D" "40" "40" "chamfer")) 
(defun c:cc45() (command "chamfer" "D" "45" "45" "chamfer"))
(defun c:cc50() (command "chamfer" "D" "50" "50" "chamfer")) 
(defun c:cc55() (command "chamfer" "D" "55" "55" "chamfer")) 
(defun c:cc60() (command "chamfer" "D" "60" "60" "chamfer")) 
(defun c:cc65() (command "chamfer" "D" "65" "65" "chamfer")) 
(defun c:cc70() (command "chamfer" "D" "70" "70" "chamfer")) 
(defun c:cc75() (command "chamfer" "D" "75" "75" "chamfer")) 
(defun c:cc80() (command "chamfer" "D" "80" "80" "chamfer")) 
(defun c:cc85() (command "chamfer" "D" "85" "85" "chamfer")) 
(defun c:cc90() (command "chamfer" "D" "90" "90" "chamfer")) 
(defun c:cc95() (command "chamfer" "D" "95" "95" "chamfer")) 
(defun c:cc100() (command "chamfer" "D" "100" "100" "chamfer"))
