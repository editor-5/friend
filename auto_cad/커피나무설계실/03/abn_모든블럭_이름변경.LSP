(defun c:abn ( / key txt op oDocument )
  (prompt "\n블럭이름 일괄변경하기 ...")
  (initget "Front Back")
  (setq key (getkword "\n앞에넣기(F)/뒤에넣기<B>: "))
  (if (= key nil) (setq key "Back"))
  (cond
    ((= key "Front") (setq op "앞에"))
    ((= key "Back") (setq op "뒤에"))
  )
  (setq txt (getstring (strcat "\n" op " 추가할 이름 입력: ")))
  (setq oDocument (vla-get-activedocument (vlax-get-acad-object)))
  (vlax-for oBlock (vla-get-blocks oDocument)
    (if (/= (substr (vla-get-name oBlock) 1 1) "*")
      (cond
        ((= key "Front") (vla-put-name oBlock (strcat txt (vla-get-name oBlock))))
        ((= key "Back") (vla-put-name oBlock (strcat (vla-get-name oBlock) txt)))
      )
    )
  )
  (princ)
)
(vl-load-com)
(prompt "\n[ RENBL ]")
(princ)
