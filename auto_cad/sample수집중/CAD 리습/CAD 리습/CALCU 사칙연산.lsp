(defun c:+(/ choi d_ts w_os ht ss grpt pt1 n k tot en tv rtv an)
   (setq choi (getvar "orthomode")  d_ts (getvar "textsize")
            w_os (getvar "osmode") )
   (setvar "orthomode" 0) (setvar "osmode" 0)
   (setq ht d_ts)
         (setq lts1 (getvar "ltscale"))
         (setq lts (* 2 lts1))
   (prompt "\nText Height<") (prin1 ht) (prompt ">: ")
   (setq ht (getdist))
   (if (= ht nil) (setq ht d_ts))
   (prompt "\nSelect number->")
   (setq ss (ssget))
   (setq grpt (grread T))
   (setq pt1 (cadr grpt))
   (setq n (sslength ss))
   (setq k 0 tot 0)
   (while (<= 1 n)
        (setq en (ssname ss k))
        (setq tv (cdr (assoc 1 (entget en))))

        (setq kn (strlen tv))

        (if (/= (wcmatch tv "*,*") nil)(progn
        (setq kk 2)
        (setq a0 (substr tv KK 1))
        (while (and (/= a0 ",")(<= kk kn))
        (setq kk (+ kk 1))
   (prompt "\nSelect number->")
   (princ tv)
        (setq a0 (substr tv KK 1))
               )
               (if (= a0 ",")(progn
                   (setq a1 (substr tv 1 (- kk 1)))
                   (setq a2 (substr tv (+ kk 1) (- kn kk)))
                   (setq tv (strcat a1 a2))
;                   (entmod (subst (cons 1 tv) (assoc 1 (entget en))(entget en)))

(prompt "\nSelect number122221->")
   (princ tv)
               ))
           ))

  (prompt "\nSelect number11111->")
   (princ tv)

        (setq rtv (atof tv))
        (setq tot (+ tot rtv))
        (setq n (- n 1))
        (setq k (+ k 1))
   )
   (setq tot (rtos tot 2 3))
   (prompt "\nÇÕ °è : ") (prin1 tot)
         (setvar "osmode" 0)

    (setq p12 (getpoint "\nEnter text point->"))
    (command "text" "j" "r" p12 lts "0" tot)
)

(defun c:-(/ ot ts os ht ss1 en1 ent1 tv1 ss2 en2 ent2 tv2 grpt pt1 rst1
                      tot1 rtv1 rtv2 en an)
   (setq ot (getvar "orthomode")  ts (getvar "textsize")
            os (getvar "osmode") )
   (setvar "orthomode" 0) (setvar "osmode" 0)
   (setq ht ts)
   (prompt "\nText Height<") (prin1 ht) (prompt ">: ")
   (setq ht (getdist))
   (if (= ht nil) (setq ht ts))
   (prompt "\nSelect first number->")
   (setq ss1 (entsel) en1 (car ss1))   (redraw en1 3)
   (setq ent1 (assoc 1 (entget (car ss1))))
   (setq tv1 (cdr ent1))
   (prompt "\nSelect second number->")
   (setq ss2 (entsel) en2 (car ss2))   (redraw en2 3)
   (setq ent2 (assoc 1 (entget (car ss2))))
   (setq tv2 (cdr ent2))
   (setq grpt (grread T) pt1 (cadr grpt))
   (setq  rst1 0)
   (setq rtv1 (atof tv1)  rtv2 (atof tv2))
   (setq rst1 (- rtv1 rtv2))
   (setq tot1 (abs rst1))
   (setq tot1 (rtos tot1 2 3))
   (if (= (wcmatch tot1 "*.*") nil)
       (setq tot1 (strcat tot1 ".00")))
   (setq an (strlen tot1))
   (if (= (substr tot1 (- an 1) 1) ".")
       (setq tot1 (strcat tot1 "0")) )
   (if (< rst1 0)
       (setq tot1 (strcat "-" tot1)))
   (prompt "\n°á °ú : ") (prin1 rst1)
   (command "text" "j" "r" pt1 ht "0" tot1)
   (redraw en1 4) (redraw en2 4)
   (prompt "\nEnter text point->")
   (command "move" "l" "" pt1 pause)
   (setvar "orthomode" ot) (setvar "osmode" os)
   (prin1)
)

(defun c:*(/ choi d_ts w_os ht ss grpt pt1 n k tot en tv rtv an)
   (setq choi (getvar "orthomode")  d_ts (getvar "textsize")
            w_os (getvar "osmode") )
   (setvar "orthomode" 0) (setvar "osmode" 0)
   (setq ht d_ts)
;   (prompt "\nText Height<") (prin1 ht) (prompt ">: ")
;   (setq ht (getdist))
    (setq tot 1)

  (prompt "\nSelect number11111->")
   (princ tot)

;   (if (= ht nil) (setq ht d_ts))
   (prompt "\nSelect number->")
   (setq ss (ssget))
   (setq grpt (grread T))
   (setq pt1 (cadr grpt))
   (setq n (sslength ss))
   (setq k 0 tot 1)
   (while (<= 1 n)
        (setq en (ssname ss k))
        (setq tv (cdr (assoc 1 (entget en))))

        (setq kn (strlen tv))

        (if (/= (wcmatch tv "*,*") nil)(progn
        (setq kk 2)
        (setq a0 (substr tv KK 1))
        (while (and (/= a0 ",")(<= kk kn))
        (setq kk (+ kk 1))
   (prompt "\nSelect number->")
   (princ tv)
        (setq a0 (substr tv KK 1))
               )
               (if (= a0 ",")(progn
                   (setq a1 (substr tv 1 (- kk 1)))
                   (setq a2 (substr tv (+ kk 1) (- kn kk)))
                   (setq tv (strcat a1 a2))
;                   (entmod (subst (cons 1 tv) (assoc 1 (entget en))(entget en)))

(prompt "\nSelect number122221->")
   (princ tv)
               ))
           ))

  (prompt "\nSelect number11111->")
   (princ tot)

        (setq rtv (atof tv))
        (setq tot (* tot rtv))
        (setq n (- n 1))
        (setq k (+ k 1))
   )
   (setq tot (rtos tot 2 3))
   (prompt "\nÇÕ °è : ") (prin1 tot)
         (setvar "osmode" 0)

     (setq p12 (getpoint "\nEnter text point->"))
    (command "text" "j" "r" p12 ht "0" tot)
)


(defun c:/(/ choi d_ts w_os ht ss1 en1 ent1 tv1 ss2 en2 ent2 tv2 grpt pt1 rst1
                      tot1 rtv1 rtv2 en an)
   (setq choi (getvar "orthomode")  d_ts (getvar "textsize")
            w_os (getvar "osmode") )
   (setvar "orthomode" 0) (setvar "osmode" 0)
   (setq ht d_ts)
   (prompt "\nText Height<") (prin1 ht) (prompt ">: ")
   (setq ht (getdist))
   (if (= ht nil) (setq ht d_ts))
   (prompt "\nSelect first number->")
   (setq ss1 (entsel) en1 (car ss1))   (redraw en1 3)
   (setq ent1 (assoc 1 (entget (car ss1))))
   (setq tv1 (cdr ent1))
   (prompt "\nSelect second number->")
   (setq ss2 (entsel) en2 (car ss2))   (redraw en2 3)
   (setq ent2 (assoc 1 (entget (car ss2))))
   (setq tv2 (cdr ent2))
   (setq grpt (grread T) pt1 (cadr grpt))
   (setq  rst1 0)
   (setq rtv1 (atof tv1)  rtv2 (atof tv2))
   (setq rst1 (/ rtv1 rtv2));³ª´©±â
   (setq tot1 (abs rst1))
   (setq tot1 (rtos tot1 2 5));ÀÚ¸®¼ö
   (if (= (wcmatch tot1 "*.*") nil)
       (setq tot1 (strcat tot1 ".000")))
   (setq an (strlen tot1))
   (if (= (substr tot1 (- an 1) 1) ".")
       (setq tot1 (strcat tot1 "0")) )
   (if (< rst1 0)
       (setq tot1 (strcat "-" tot1)))
   (prompt "\n°á °ú : ") (prin1 rst1)
   (command "text" "j" "r" pt1 ht "0" tot1)
   (redraw en1 4) (redraw en2 4)
   (prompt "\nEnter text point->")
   (command "move" "l" "" pt1 pause)
   (setvar "orthomode" choi) (setvar "osmode" w_os)
   (prompt "\n°á °ú : ") (prin1 rst1)
   (prin1)
)
