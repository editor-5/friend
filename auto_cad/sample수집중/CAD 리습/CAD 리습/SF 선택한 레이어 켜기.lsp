;;================================================
;  SELECT FREEZE(9812cho_i)
;;------------------------------------------------
(defun c:sf(/ ss n k en cly oly)
   (prompt "\nCommand: select Preeze...")
   (prompt "\n켤 레이어만을 선택-> ")
   (setq ss (ssget))
   (setq n (sslength ss))
   (setq k 0)
   (setq cly (cdr (assoc 8 (entget (ssname ss (1- n))))))
   (command "layer" "s" cly "")
   (command "layer" "off" "*" "" "")
   (while (<= 1 n)
       (setq en (ssname ss k))
       (setq oly (cdr (assoc 8 (entget en))))
       (command "layer" "on" oly "")
       (setq n (- n 1))
       (setq k (+ k 1))
    )
    (princ)
)
