;;;길이의 합을 지정위치에 표기
(DEFUN C:ds(/ eg egl n l ne entname entn p1 p2 l2 radi l_ength)
      (SETVAR "cmdecho" 0)
      (setvar "blipmode" 0)
	(SETQ EG (SSGET))
	(SETQ EGL (SSLENGTH EG))
	(SETQ N 0)
	(setq l 0)
	(setq ne 0)
	(WHILE (< N EGL)
		(SETQ ENTN (SSNAME EG N))
		(SETQ ENT (ENTGET ENTN))
		(setq entname (assoc 0 ent))
		(setq entname (cdr entname))
		(if (= entname "LINE")
			(progn
				(SETQ p1 (ASSOC 10 ENT))
				(SETQ p2 (ASSOC 11 ENT))
				(SETQ p1x (car (CDR p1)))
				(SETQ p1y (CaDdR p1))
				(SETQ p2x (car (CDR p2)))
				(SETQ p2y (CaDdR p2))
				(setq l2 (sqrt (+ (expt (- p1x p2x) 2) (expt (- p1y p2y) 2))))	
				(setq l (+ l l2))
				(setq  ne (+ ne 1))
			)
		)
		(if (= entname "CIRCLE")
			(progn
				(SETQ p1 (ASSOC 40 ENT))
				(SETQ radi (cdr p1))
				(setq l2 (* 2 (* pi radi)))
				(setq l (+ l l2))
				(setq  ne (+ ne 1))
			)
		)
  ;(defun arc_calc ()
  ;  (setq totang (- end_ang st_ang))
  ;  (while (< totang 0)
  ;    (setq totang (+ totang (* 2 pi)))
  ;  )
  ;  (while (> totang (* 2 pi))
  ;    (setq totang (- totang (* 2 pi)))
  ;  )
  ;  (set_tile "tot_angle" (angtos totang))
  ;  (setq arclen (* (* 2 pi radius) (/ totang (* 2 pi))))
  ;  (set_tile "arclen" (rtos arclen))
  ;)
				(if (= entname "ARC")
			(progn
				(SETQ p1 (ASSOC 40 ENT))
				(SETQ radi (cdr p1))
				(SETQ p1 (ASSOC 50 ENT))
				(SETQ p2 (ASSOC 51 ENT))
				(SETQ p1R (CDR p1))
				(SETQ p2R (CDR p2))
				(SETQ TH (- P2R P1R))
				(WHILE (< TH 0)
				  (SETQ TH (+ TH (* 2 PI)))
				)
				(WHILE (> TH (* 2 PI))
				  (SETQ TH (- TH (* 2 PI)))
				)
				(SETQ l2 (*(* 2 PI RADI)(/ TH (* 2 PI))))
				;(SETQ TH (ABS (- P1R P2R)))
				;(setq l2 (* RADI TH))
				(setq l (+ l l2))
				(setq  ne (+ ne 1))
			)
		)
            (if (or (= entname "LWPOLYLINE")(= entname "POLYLINE"))
                  (progn
     		            (command "area" "e" entn)
            	      (setq l2 (getvar "perimeter"))
				(setq l (+ l l2))
				(setq  ne (+ ne 1))
	            )
            ) 
		(SETQ N (+ 1 N))
	)
	(princ "\n >>>>> ")
	(if (> egl ne)
		(progn
			(princ ne)(princ " of ")(princ egl)
			(princ " objects are measured // ")
		)
	)
	(princ " Total length is  ")
	(setq l_ength (rtos (/ l 1000) 2 2))
	(prin1 l_ength)
        (setq pt (getpoint "\nText Point: "))
               (setq h (getvar "textsize"))
               (prompt "\nText Height: ")
               (princ H)
               (princ "  : ")
               (setq z (getdist))
               (if z
                   (setq h z)
               )
;               (setvar "textsize" h)
;               (command "text" pt 0.0 l_ength)
               (command "text"
                        (setq z pt)
                        (setq z h)
                        (setq z 0.0)
                        (setq z l_ength)
               )
	(setvar "cmdecho" 1)
	(setvar "blipmode" 0)
	(command "regen")
	(princ)
)
