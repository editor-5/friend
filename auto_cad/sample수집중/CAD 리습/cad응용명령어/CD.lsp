;**************change text (digitaze)******************************
(defun c:CD (/ s l chk index l n s2 high olderr )
   (setq olderr  *error*
	 *error* chgterr)
   (setq s (ssget))
       (if (/= s nil)
	 (progn
	   (setq l (sslength s))
	   (setq n (entget (car (entsel "\nSelect Text :"))))
	   (setq high (cdr (assoc 1 n)))
	   (setq index 0)
	   (setvar "cmdecho" 0)
	   (command "undo" "group")
	   (repeat l
		  (setq s2 (entget (ssname s index)))
		  (setq index (1+ index))
		  (setq chk (cdr (assoc 0 s2)))
		  (if (= chk "TEXT")
		      (progn
			   (setq s2(subst (cons 1 high) (assoc 1 s2) s2))
			   (entmod s2)
		      )
		   )
	   )
	   (command "undo" "end")
	   (setvar "cmdecho" 1)
	 )
      )
  (setq *error* olderr)
  (princ)
)
