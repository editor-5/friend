(defun c:set()
  (setq a (entsel) na (car a) naa (entget na) lay (assoc 8 naa) la (cdr lay)
                                              lac (assoc 62 naa) ca (cdr lac))
  (if (= ca nil) (setq ca "byla"))
  (command "layer" "s" la "" "color" ca))
(defun c:sl()
   (setq a (entsel) na (car a) naa (entget na) lay (assoc 8 naa) la (cdr lay))
   (command "layer" "s" la ""))
(defun c:sc()
   (setq a (entsel) na (car a) naa (entget na) lac (assoc 62 naa) ca (cdr lac))
   (if (= ca nil) (setq ca "byla"))
   (command "color" ca))
(defun c:ww() (command "layer" "of" "*" "" ""))
(defun c:AT() (command "layer" "on" "*" ""))
(defun c:w00() (command "layer" "t" "*" ""))
(defun c:w1()
   (setq a (entsel) na (car a) naa (entget na) lay (assoc 8 naa) la (cdr lay))    
   (command "layer" "s" la "of" "*" "" ""))
(defun c:w11()
   (setq a (entsel) na (car a) naa (entget na) lay (assoc 8 naa) la (cdr lay))
   (command "layer" "s" la "f" "*" "" ""))
(defun c:w2() (command "layer" "of" "*" "" "on" "w_*,s_*" ""))
(defun c:w22() (command "layer" "f" "*" "t" "w_*" "on" "w_*" ""))
(defun c:w4() 
   (setq a (entsel) na (car a) naa (entget na) lay (assoc 8 naa) la (cdr lay))
   (command "layer" "of" la "") (princ la))
(defun c:w5 ()
   (command "layer" "on" "*" "of" "W_*,s_*" "" ""))
(defun c:w44()
   (setq a (entsel) na (car a) naa (entget na) lay (assoc 8 naa) la (cdr lay))
   (command "layer" "t" "0" "s" "0" "f" la ""))
