;;===========================================================
; 선택된 Line의 길이을 모두 더하는 명령(000822cho_i)
;;-----------------------------------------------------------
(defun c:lp(/  ss en n n1 k tot dis dis1)
   (prompt "\nCommand: Line Plus...")
   (prompt "\n더하고자하는 line을 선택-> ")
   (setq ss (ssget))
   (setq n1 (sslength ss))
   (setq n n1 k 0)
   (setq tot 0 dis 0 dis1 0)
   (while (<= 1 n)
       (setq en (ssname ss k))
       (setq stype (cdr (assoc 0 (entget en))))
       (if (= stype "LINE")(progn
           (setq spt (cdr (assoc 10 (entget en))))
           (setq ept (cdr (assoc 11 (entget en))))
           (setq dis1 (distance spt ept))
           (setq dis (/ dis1 1000.0))(prin1 dis)
       ))(terpri)
       (if (= stype "LWPOLYLINE")(progn
           (command "area" "e" en)
           (setq dis1 (getvar "perimeter"))
           (setq dis (/ dis1 1000.0))
       ))
       (setq tot (+ tot dis))
       (setq n (- n 1))
       (setq k (+ k 1))
    )(terpri)(prompt "총")(prin1 n1)(prompt "개의 라인...")
    (prompt "전체길이 : ")(prin1 tot)(prompt " m")
    (prin1)
)
;자료제공 : 아키모아(http://www.Archimore.com/)
