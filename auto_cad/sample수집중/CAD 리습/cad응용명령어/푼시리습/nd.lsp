;;=========================================================
; Number divide('0106cho_i)
; ->두 수의 나누기 구하기(2자리)
;   작은수을 큰수로 나누면 percent(--%)로 표시됨
;;---------------------------------------------------------
(defun c:nd(/  myerror choi d_ts w_os ht ss1 en1 ent1 tv1 ss2 en2 ent2
             tv2 grpt pt1 rst1 tot1 rtv1 rtv2 en an)
;start --- Internal error handler ----------
 (defun myerror(S)
 (if (/= s "Function cancelled")(princ (strcat "\nError:" s)))
 (setvar "osmode" w_os)
 (setq *error* olderr)(princ) )
 (setq olderr *error* *error* myerror)
;end----------------------------------------
   (prompt "... 나누기")
   (setq choi (getvar "orthomode")  d_ts (getvar "textsize")
            w_os (getvar "osmode") )
   (setvar "orthomode" 0) (setvar "osmode" 0)
   (setq ht d_ts)
   (prompt "\nText Height<") (prin1 ht) (prompt ">: ")
   (setq ht (getdist))
   (if (= ht nil) (setq ht d_ts))
   (prompt "\nSelect first number->")
   (setq ss1 (entsel) en1 (car ss1))   (redraw en1 3)
   (setq ent1 (assoc 1 (entget (car ss1))))
   (setq tv1 (cdr ent1))
   (prompt "\nSelect second number->")
   (setq ss2 (entsel) en2 (car ss2))   (redraw en2 3)
   (setq ent2 (assoc 1 (entget (car ss2))))
   (setq tv2 (cdr ent2))
   (setq grpt (grread T) pt1 (cadr grpt))
   (setq  rst1 0)
   (setq rtv1 (atof tv1)  rtv2 (atof tv2))
   (setq rst1 (/ rtv1 rtv2));나누기
   (if (< rtv1 rtv2) (setq rst1 (* rst1 100)))
   (setq tot1 (abs rst1))
   (setq tot1 (rtos tot1 2 2))
   (if (= (wcmatch tot1 "*.*") nil)
       (setq tot1 (strcat tot1 ".00")))
   (setq an (strlen tot1))
   (if (= (substr tot1 (- an 1) 1) ".")
       (setq tot1 (strcat tot1 "0")) )
   (if (< rst1 0)
       (setq tot1 (strcat "-" tot1)))
   (command "text" "j" "r" pt1 ht "0" tot1)
   (redraw en1 4) (redraw en2 4)
   (prompt "\nEnter text point->")
   (command "move" "l" "" pt1 pause)
   (setvar "orthomode" choi) (setvar "osmode" w_os)
   (prompt "\n결 과 : ")(prin1 rtv1)(prompt "/")
   (prin1 rtv2)(prompt "= ") (prin1 rst1)
   (if (< rtv1 rtv2)(progn
       (prompt "\n결 과 : ")(prin1 rtv1)(prompt "/")(prin1 rtv2)
       (prompt "*100")(prompt "= ") (prin1 rst1)(prompt"%")
   ))
   (prin1)
)
