(defun c:XY ()
 (setq ts (getvar "textsize"))
 (setq osm (getvar "osmode"))
 (setq pt1 (getpoint "Pick First Point:"))
 (setq pt2 (getpoint pt1 "Pick Second Point:"))
 (setvar "osmode" 0) 
 (setq px (car pt1))
 (setq py (cadr pt1))
 (setq pxt (strcat "X=" (rtos py 2 4)))
 (setq pyt (strcat "Y=" (rtos px 2 4)))
 (command "line" pt1 pt2 "")
 (setq txtpnt pt2)
 (setq txtpnt1 (list (car txtpnt)
 (- (cadr txtpnt) (* 1.5 ts)) 0.0))
 (command ".text" "j" "bl" txtpnt ts "" pxt)
 (command ".text" "j" "bl" txtpnt1 ts "" pyt)
 (setvar "osmode" osm)
 (princ)
)
